FME workspace daten_kopieren.fmw

Parameters:
- DestDataset_POSTGIS = geo_fme_r@gv-srv-w00118   # Verbindung

Readers:
- GEODATABASE_SDE_1: GEODATABASE_SDE
- GEODATABASE_SDE_2: GEODATABASE_SDE

Writers:
- POSTGIS_1: POSTGIS to $(DestDataset_POSTGIS)

hdu01_b (reader GEODATABASE_SDE_1)
    attributes: OBJECTID integer, LAND char(3), OBJART_1 char(5), OBJID_1 char(16), EBENE_1 char(7), OBJART_2 char(5), OBJID_2 char(16), EBENE_2 char(7)
    -> BulkAttributeRenamer_4
BulkAttributeRenamer_4
    CASE_CHANGE_TYPE = lower
    ATTRCHOICE = All Attributes
    PATTERN_ACTION_DISP = CASECHANGE
    MODE_CHOICE = RENAME
    -> sdp.hdu01_b (writer POSTGIS_1)
sdp.hdu01_b (writer POSTGIS_1)
    attributes: objectid int4, land varchar(3), objart_1 varchar(5), objid_1 varchar(16), ebene_1 varchar(7), objart_2 varchar(5), objid_2 varchar(16), ebene_2 varchar(7)
ver01_f (reader GEODATABASE_SDE_1)
    attributes: OBJECTID integer, LAND char(3), MODELLART char(30), OBJART char(5), OBJART_TXT char(50), OBJID char(16), HDU_X smallint, BEGINN char(20), ENDE char(20), FKT char(4), NAM char(60), STS char(20), ZNM char(60), SHAPE.STArea() double, SHAPE.STLength() double
    -> BulkAttributeRenamer_2
BulkAttributeRenamer_2
    CASE_CHANGE_TYPE = lower
    ATTRCHOICE = All Attributes
    PATTERN_ACTION_DISP = CASECHANGE
    MODE_CHOICE = RENAME
    -> sdp.ver01_f (writer POSTGIS_1)
sdp.ver01_f (writer POSTGIS_1)
    attributes: objectid int4, land varchar(3), modellart varchar(30), objart varchar(5), objart_txt varchar(50), objid varchar(16), hdu_x int2, beginn varchar(20), ende varchar(20), fkt varchar(4), nam varchar(60), sts varchar(20), znm varchar(60)
ver06_f (reader GEODATABASE_SDE_1)
    attributes: OBJECTID integer, LAND char(3), MODELLART char(30), OBJART char(5), OBJART_TXT char(50), OBJID char(16), HDU_X smallint, BEGINN char(20), ENDE char(20), ART char(4), BEZ char(180), BFK char(4), BRO double, BWF char(4), DHU double, KMA double, NAM char(60), OFM char(4), STS char(20), ZNM char(60), ZUS char(4), SHAPE.STArea() double, SHAPE.STLength() double
    -> BulkAttributeRenamer_5
BulkAttributeRenamer_5
    CASE_CHANGE_TYPE = lower
    ATTRCHOICE = All Attributes
    PATTERN_ACTION_DISP = CASECHANGE
    MODE_CHOICE = RENAME
    -> sdp.ver06_f (writer POSTGIS_1)
sdp.ver06_f (writer POSTGIS_1)
    attributes: objectid int4, land varchar(3), modellart varchar(30), objart varchar(5), objart_txt varchar(50), objid varchar(16), hdu_x int2, beginn varchar(20), ende varchar(20), art varchar(4), bez varchar(180), bfk varchar(4), bro float8, bwf varchar(4), dhu float8, kma float8, nam varchar(60), ofm varchar(4), sts varchar(20), znm varchar(60), zus varchar(4)
ver06_l (reader GEODATABASE_SDE_1)
    attributes: OBJECTID integer, LAND char(3), MODELLART char(30), OBJART char(5), OBJART_TXT char(50), OBJID char(16), HDU_X smallint, BEGINN char(20), ENDE char(20), ART char(4), BEZ char(180), BFK char(4), BRO double, BWF char(4), DHU double, KMA double, NAM char(60), OFM char(4), STS char(20), ZNM char(60), ZUS char(4), SHAPE.STLength() double
    -> BulkAttributeRenamer
BulkAttributeRenamer
    CASE_CHANGE_TYPE = lower
    ATTRCHOICE = All Attributes
    PATTERN_ACTION_DISP = CASECHANGE
    MODE_CHOICE = RENAME
    -> sdp.ver06_l (writer POSTGIS_1)
sdp.ver06_l (writer POSTGIS_1)
    attributes: objectid int4, land varchar(3), modellart varchar(30), objart varchar(5), objart_txt varchar(50), objid varchar(16), hdu_x int2, beginn varchar(20), ende varchar(20), art varchar(4), bez varchar(180), bfk varchar(4), bro float8, bwf varchar(4), dhu float8, kma float8, nam varchar(60), ofm varchar(4), sts varchar(20), znm varchar(60), zus varchar(4)
veg01_f (reader GEODATABASE_SDE_1)
    attributes: OBJECTID integer, LAND char(3), MODELLART char(30), OBJART char(5), OBJART_TXT char(50), OBJID char(16), HDU_X smallint, BEGINN char(20), ENDE char(20), VEG char(4), SHAPE.STArea() double, SHAPE.STLength() double
    -> BulkAttributeRenamer_3
BulkAttributeRenamer_3
    CASE_CHANGE_TYPE = lower
    ATTRCHOICE = All Attributes
    PATTERN_ACTION_DISP = CASECHANGE
    MODE_CHOICE = RENAME
    -> sdp.veg01_f (writer POSTGIS_1)
sdp.veg01_f (writer POSTGIS_1)
    attributes: objectid int4, land varchar(3), modellart varchar(30), objart varchar(5), objart_txt varchar(50), objid varchar(16), hdu_x int2, beginn varchar(20), ende varchar(20), veg varchar(4)
veg02_f (reader GEODATABASE_SDE_1)
    attributes: OBJECTID integer, LAND char(3), MODELLART char(30), OBJART char(5), OBJART_TXT char(50), OBJID char(16), HDU_X smallint, BEGINN char(20), ENDE char(20), BEZ char(60), NAM char(60), VEG char(4), ZUS char(4), SHAPE.STArea() double, SHAPE.STLength() double
    -> BulkAttributeRenamer_7
BulkAttributeRenamer_7
    CASE_CHANGE_TYPE = lower
    ATTRCHOICE = All Attributes
    PATTERN_ACTION_DISP = CASECHANGE
    MODE_CHOICE = RENAME
    -> sdp.veg02_f (writer POSTGIS_1)
sdp.veg02_f (writer POSTGIS_1)
    attributes: objectid int4, land varchar(3), modellart varchar(30), objart varchar(5), objart_txt varchar(50), objid varchar(16), hdu_x int2, beginn varchar(20), ende varchar(20), bez varchar(60), nam varchar(60), veg varchar(4), zus varchar(4)
veg03_f (reader GEODATABASE_SDE_1)
    attributes: OBJECTID integer, LAND char(3), MODELLART char(30), OBJART char(5), OBJART_TXT char(50), OBJID char(16), HDU_X smallint, BEGINN char(20), ENDE char(20), FKT char(4), NAM char(60), OFM char(4), SHAPE.STArea() double, SHAPE.STLength() double
    -> BulkAttributeRenamer_6
BulkAttributeRenamer_6
    CASE_CHANGE_TYPE = lower
    ATTRCHOICE = All Attributes
    PATTERN_ACTION_DISP = CASECHANGE
    MODE_CHOICE = RENAME
    -> sdp.veg03_f (writer POSTGIS_1)
sdp.veg03_f (writer POSTGIS_1)
    attributes: objectid int4, land varchar(3), modellart varchar(30), objart varchar(5), objart_txt varchar(50), objid varchar(16), hdu_x int2, beginn varchar(20), ende varchar(20), fkt varchar(4), nam varchar(60), ofm varchar(4)
sie02_f (reader GEODATABASE_SDE_1)
    attributes: OBJECTID integer, LAND char(3), MODELLART char(30), OBJART char(5), OBJART_TXT char(50), OBJID char(16), HDU_X smallint, BEGINN char(20), ENDE char(20), AGT char(4), BEB char(4), BEZ char(60), FGT char(4), FKT char(4), NAM char(100), PEG char(4), ZNM char(60), ZUS char(4), SHAPE.STArea() double, SHAPE.STLength() double
    -> BulkAttributeRenamer_8
BulkAttributeRenamer_8
    CASE_CHANGE_TYPE = lower
    ATTRCHOICE = All Attributes
    PATTERN_ACTION_DISP = CASECHANGE
    MODE_CHOICE = RENAME
    -> sdp.sie02_f (writer POSTGIS_1)
sdp.sie02_f (writer POSTGIS_1)
    attributes: objectid int4, land varchar(3), modellart varchar(30), objart varchar(5), objart_txt varchar(50), objid varchar(16), hdu_x int2, beginn varchar(20), ende varchar(20), agt varchar(4), beb varchar(4), bez varchar(60), fgt varchar(4), fkt varchar(4), nam varchar(100), peg varchar(4), znm varchar(60), zus varchar(4)
ver02_l (reader GEODATABASE_SDE_1)
    attributes: OBJECTID integer, LAND char(3), MODELLART char(30), OBJART char(5), OBJART_TXT char(50), OBJID char(16), HDU_X smallint, BEGINN char(20), ENDE char(20), ART char(4), BEF char(4), BEZ char(60), BRV integer, FKT char(4), MKG char(4), NAM char(60), STS char(20), ZNM char(60), SHAPE.STLength() double
    -> BulkAttributeRenamer_9
BulkAttributeRenamer_9
    CASE_CHANGE_TYPE = lower
    ATTRCHOICE = All Attributes
    PATTERN_ACTION_DISP = CASECHANGE
    MODE_CHOICE = RENAME
    -> sdp.ver02_l (writer POSTGIS_1)
sdp.ver02_l (writer POSTGIS_1)
    attributes: objectid int4, land varchar(3), modellart varchar(30), objart varchar(5), objart_txt varchar(50), objid varchar(16), hdu_x int2, beginn varchar(20), ende varchar(20), art varchar(4), bef varchar(4), bez varchar(60), brv int4, fkt varchar(4), mkg varchar(4), nam varchar(60), sts varchar(20), znm varchar(60)
ver01_l (reader GEODATABASE_SDE_1)
    attributes: OBJECTID integer, LAND char(3), MODELLART char(30), OBJART char(5), OBJART_TXT char(50), OBJID char(16), HDU_X smallint, BEGINN char(20), ENDE char(20), OBJART_Z char(5), OBJID_Z char(16), BDI char(4), BDU char(4), BVB char(4), BEZ char(30), BFS char(4), BRF double, BRV integer, FKT char(4), FSZ integer, FTR char(4), IBD char(4), NAM char(60), OFM char(4), STS char(40), WDM char(4), ZNM char(60), ZUS char(4), SHAPE.STLength() double
    -> BulkAttributeRenamer_10
BulkAttributeRenamer_10
    CASE_CHANGE_TYPE = lower
    ATTRCHOICE = All Attributes
    PATTERN_ACTION_DISP = CASECHANGE
    MODE_CHOICE = RENAME
    -> sdp.ver01_l (writer POSTGIS_1)
sdp.ver01_l (writer POSTGIS_1)
    attributes: objectid int4, land varchar(3), modellart varchar(30), objart varchar(5), objart_txt varchar(50), objid varchar(16), hdu_x int2, beginn varchar(20), ende varchar(20), objart_z varchar(5), objid_z varchar(16), bdi varchar(4), bdu varchar(4), bvb varchar(4), bez varchar(30), bfs varchar(4), brf float8, brv int4, fkt varchar(4), fsz int4, ftr varchar(4), ibd varchar(4), nam varchar(60), ofm varchar(4), sts varchar(40), wdm varchar(4), znm varchar(60), zus varchar(4)
SDP.ALKIS__Nutzung_Flaechen (reader GEODATABASE_SDE_2)
    attributes: OBJECTID integer, REGID integer, UUID char(16), UNV char(254), LAN char(2), NAMLAN char(254), RBZ char(1), NAMRBZ char(254), KRS char(5), NAMKRS char(254), GEM char(8), NAMGEM char(254), LAG char(19), NAMLAG char(254), BEZ char(254), NAM char(254), ZNM char(254), FKT smallint, BEZFKT char(64), BEB smallint, BEZBEB char(64), ZUS smallint, BEZZUS char(64), VEG smallint, BEZVEG char(64), AGT smallint, BEZAGT char(64), LGT smallint, BEZLGT char(64), OFM smallint,
      BEZOFM char(64), HYD smallint, BEZHYD char(64), FGT smallint, BEZFGT char(64), ART smallint, BEZART char(64), PEG smallint, BEZPEG char(64), NTZ smallint, BEZNTZ char(64), STS char(32), TID smallint, BEZTID char(64), GWK char(254), IDN char(254), WDM smallint, BEZWDM char(64), SFK smallint, BEZSFK char(64), BDI smallint, BEZBDI char(64), BDU smallint, BEZBDU char(64), BFS smallint, BEZBFS char(64), BRF double, BRV integer, FSZ integer, BEF smallint,
      BEZBEF char(64), MKG smallint, BEZMKG char(64), FTR smallint, BEZFTR char(64), IBD smallint, BEZIDB char(64), BKT char(32), BEZBKT char(254), ELK smallint, BEZELK char(64), NRB char(254), GLS smallint, SPW double, FLR char(5), BRG integer, DES char(4), BEZDES char(140), FDV char(4), SNR char(50), DPRIO char(20), POS char(20), DVAR char(20), KENN char(32), BEZEICH char(64), KENNZUSO char(32), BEG date, ENDE date, MAT char(64), STM char(64),
      CRS char(50), STATUS char(10), STATUSDAT date, Shape.STArea() double, Shape.STLength() double
    -> BulkAttributeRenamer_11
BulkAttributeRenamer_11
    CASE_CHANGE_TYPE = lower
    ATTRCHOICE = All Attributes
    PATTERN_ACTION_DISP = CASECHANGE
    MODE_CHOICE = RENAME
    -> alkis_nutzung_flaechen (writer POSTGIS_1)
alkis_nutzung_flaechen (writer POSTGIS_1)
    attributes: objectid int4, regid varchar(200), uuid varchar(200), unv varchar(200), lan varchar(200), namlan varchar(200), rbz varchar(200), namrbz varchar(200), krs varchar(200), namkrs varchar(200), gem varchar(200), namgem varchar(200), lag varchar(200), namlag varchar(200), bez varchar(30), nam varchar(60), znm varchar(60), fkt varchar(4), bezfkt varchar(200), beb varchar(200), bezbeb varchar(200), zus varchar(4), bezzus varchar(200), veg varchar(200), bezveg varchar(200), agt varchar(200), bezagt varchar(200), lgt varchar(200), bezlgt varchar(200), ofm varchar(4),
      bezofm varchar(200), hyd varchar(200), bezhyd varchar(200), fgt varchar(200), bezfgt varchar(200), art varchar(200), bezart varchar(200), peg varchar(200), bezpeg varchar(200), ntz varchar(200), bezntz varchar(200), sts varchar(40), tid varchar(200), beztid varchar(200), gwk varchar(200), idn varchar(200), wdm varchar(4), bezwdm varchar(200), sfk varchar(200), bezsfk varchar(200), bdi varchar(4), bezbdi varchar(200), bdu varchar(4), bezbdu varchar(200), bfs varchar(4), bezbfs varchar(200), brf float8, brv int4, fsz int4, bef varchar(200),
      bezbef varchar(200), mkg varchar(200), bezmkg varchar(200), ftr varchar(4), bezftr varchar(200), ibd varchar(4), bezidb varchar(200), bkt varchar(200), bezbkt varchar(200), elk varchar(200), bezelk varchar(200), nrb varchar(200), gls varchar(200), spw varchar(200), flr varchar(200), brg varchar(200), des varchar(200), bezdes varchar(200), fdv varchar(200), snr varchar(200), dprio varchar(200), pos varchar(200), dvar varchar(200), kenn varchar(200), bezeich varchar(200), kennzuso varchar(200), beg varchar(200), ende varchar(20), mat varchar(200), stm varchar(200),
      crs varchar(200), status varchar(200), statusdat varchar(200)
